(defun c:test-dwf ()
  (vl-load-com)
  (setq newName (strcat (getvar "DWGPREFIX") (vl-filename-base (getvar "DWGNAME")) ".dwf"))
  (princ (strcat "\nExporting to: " newName))
  (command "_.EXPORT" "DWF" newName)
  (princ "\nDone!")
  (command "_.QUIT" "Y")
)
(c:test-dwf)
